# -*- coding: utf-8 -*-
# make it easy to export STLs Meshes of the individually selected objects from FreeCAD

__Title__ = 'Export STLs'
__Author__ = 'David Barrett'
__Comment__= 'Adapted from Export to Slicer by Damian Łoziński'
__Version__ = '0.11'
__Date__ = '2023-03-16'
__Comment__ = 'Export selected objects to individual stl files'
__Web__ = 'https://github.com/djbazza/FreeCAD-STL-Export'
__Wiki__ = ''
__Icon__ = ''
__Help__ = 'You will need to change export path. To do so open Tools > Edit parameters > BaseApp/Preferences/Macros/Export2STLs'
__Status__ = 'Stable'
__Requires__ = 'freecad 0.2+'
__Communication__ = 'djbarrett at gmail dot com'
__Files__ = 'Export2STLs.FCMacro'

import os
import re
import subprocess
import Mesh
import MeshPart
import FreeCAD as app

MACRO_PARAMS_PATH = 'User parameter:BaseApp/Preferences/Macros/Export2STLs'
#DEFAULT_SLICER_PATH = '%USERPROFILE%/Downloads/PrusaSlicer/prusa-slicer.exe'
DEFAULT_EXPORT_PATH = '%USERPROFILE%/Documents/'
DEFAUL_MESH_FORMAT = 'stl'
DEFAULT_ANGULAR_DEFLECTION = 0.07

macro_params = app.ParamGet(MACRO_PARAMS_PATH)

# Slicing program executable. One can use different slicing software here and provide proper slicer executable location and custom flags
#slicer_path = macro_params.GetString('SlicerPath')
#if not slicer_path:
#    macro_params.SetString('SlicerPath', DEFAULT_SLICER_PATH)
#    slicer_path = DEFAULT_SLICER_PATH

# Export Path for STL File
export_path = macro_params.GetString('ExportPath')
if not export_path:
    macro_params.SetString('ExportPath', DEFAULT_EXPORT_PATH)
    export_path = DEFAULT_EXPORT_PATH

output_format = macro_params.GetString('OutputFormat');
if not output_format:
    macro_params.SetString('OutputFormat', DEFAUL_MESH_FORMAT)
    output_format = DEFAUL_MESH_FORMAT

# Angular deflection in radians. Lower value = better quality of curved shapes and bigger file size
angular_deflection = macro_params.GetFloat('AngularDeflection')
if not angular_deflection:
    macro_params.SetFloat('AngularDeflection', DEFAULT_ANGULAR_DEFLECTION)
    angular_deflection = DEFAULT_ANGULAR_DEFLECTION


def escape(text):
    return  re.sub(r'\W', '_', text)

def get_mesh_filename(doc_filename, mesh_name):
    '''Returns valid filename for temporary mesh file'''
    if doc_filename:
        dirname = os.path.dirname(doc_filename)
        filename = (
            os.path.basename(doc_filename).partition('.')[0]
            + mesh_name
            + '.'
            + output_format)
        file_path = os.path.join(dirname, filename)
    else:
        file_path = 'meshes-export.' + output_format
    return file_path


def main():
    doc = app.activeDocument()
    if not doc:
        raise RuntimeError('No active document')

    objects_to_export = Gui.Selection.getSelection()
    try:
        # Create temporary doc to store meshes so that we don't affect current doc history
        tmp_doc = app.newDocument('meshes')
        meshes = []
        #mesh_names = []
        for o in objects_to_export:
            mesh_name = o.Label
            if o.TypeId == 'Mesh::Feature':
                mesh_path = get_mesh_filename(export_path, mesh_name)
                Mesh.export(o, mesh_path)
            else:
                mesh = tmp_doc.addObject('Mesh::Feature', '{}_{}'.format(doc.Label, o.Label))
                mesh.Mesh = MeshPart.meshFromShape(o.Shape, LinearDeflection=0.1, AngularDeflection=angular_deflection, Relative=False)
                mesh_path = get_mesh_filename("C:/Users/davidb/Documents/3d printing/Export/", mesh_name)
                Mesh.export([mesh], mesh_path)
                app.Console.PrintMessage('Export2STLs: Objects exported: {}\n'.format(mesh_path))
    except:
        raise RuntimeError('No object selected')
    finally:
        app.closeDocument('meshes')

try:
    main()
except Exception as e:
    app.Console.PrintError('Export2STLs error: {}\n'.format(e))
